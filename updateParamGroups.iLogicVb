Option Explicit On
Imports Inventor.ObjectTypeEnum
Imports System.Text.RegularExpressions

Public Sub Main()
	
	Dim oUpdateParamGroup As updateParamGroup = New updateParamGroup()

End Sub

Public Class updateParamGroup
	
	Private oParameters As Parameters
	Private paramGroups As CustomParameterGroups
	Private groupNameDelimiter As String = ":"
	Private initialName As String
	Private initialGroupName As String
	Private initialGroup As Inventor.CustomParameterGroup
	Private NewGroupName As String
	Private NewName As String
	Private NewGroup As Inventor.CustomParameterGroup
	Private Quiet As Boolean = False

	Public Sub New()
		addEventHandler()

		RemoveEmptyGroups()
	End Sub

	Private Sub addEventHandler()
		Dim oModelingEvents As ModelingEvents = InventorApp.Application.ModelingEvents
		AddHandler oModelingEvents.OnParameterChange, AddressOf oModelingEvents_ParameterChange
		AddHandler oModelingEvents.OnNewParameter, AddressOf oModelEvents_OnNewParameter

		If Me.Quiet = False Then MessageBox.Show("Listening for parameter group changes")
	End Sub

	Private Sub RemoveEmptyGroups()
		GetParamGroups(InventorApp.Application.ActiveDocument)

		Dim tempGroup As CustomParameterGroup
		For Each tempGroup in paramGroups
			If IsGroupEmpty(tempGroup) Then
				DeleteGroup(tempGroup)
			End If
		Next
	End Sub

	Private Sub oModelingEvents_ParameterChange(
		oDoc As Inventor.Document,
		parameter As Parameter,
		BeforeOrAfter As EventTimingEnum,
		Context As NameValueMap,
		ByRef HandlingCode As HandlingCodeEnum
	)
	
		Select Case BeforeOrAfter
			Case kBefore
				initialName = parameter.Name

			Case kAfter
				NewName = parameter.Name
				
				If HasGroupChanged = True Then
					CleanupParameterGroup(oDoc)
					EditParameterGroup(oDoc)
				End If

			Case Else
				Exit Sub

		End Select

	End Sub

	Private Sub oModelEvents_OnNewParameter(
		oDoc As Inventor.Document,
		parameter As Parameter,
		BeforeOrAfter As EventTimingEnum,
		Context As NameValueMap,
		ByRef HandlingCode As HandlingCodeEnum
	)
	
		Select Case BeforeOrAfter
			Case kBefore

			Case kAfter
				NewName = parameter.Name
				EditParameterGroup(oDoc)

			Case Else
				Exit Sub

		End Select
	End Sub

	Private Function HasGroupChanged() As Boolean

		If ParseGroupName(initialName) <> ParseGroupName(NewName) Then
			Return true
		Else
			Return false
		End If

	End Function

	Private Sub CleanupParameterGroup(oDoc As Inventor.Document)

		if IsParameterGroupFormat(initialName) = false then
			exit sub
		end if

		initialGroupName = ParseGroupName(initialName)
		GetParamGroups(oDoc)

		If IsValidGroupName(initialName) = false Then
			Exit Sub
		End If

		initialGroup = GetGroupByName(initialGroupName)

		If DoesGroupContainParameter(NewName, initialGroup) = false Then
			Exit Sub
		End If

		RemoveParameterFromGroup(NewName, initialGroup)
			
		If IsGroupEmpty(initialGroup) Then
			DeleteGroup(initialGroup)
		End If

	End Sub

	Private Sub EditParameterGroup(oDoc As Inventor.Document)

		if IsParameterGroupFormat(NewName) = false then
			exit sub
		end if

		NewGroupName = ParseGroupName(NewName)
		GetParamGroups(oDoc)
	
		If IsValidGroupName(NewName) = false Then
			Exit Sub
		End If

		If DoesParameterExist(NewGroupName) = true Then
			Exit Sub
		End If

		If DoesGroupExist(NewGroupName) = false Then
			AddGroup(NewGroupName)
		End If
	
		NewGroup = GetGroupByName(NewGroupName)
	
		If DoesGroupContainParameter(NewName, NewGroup) = false Then
			AddParameterToGroup(NewName, NewGroup)
			If Me.Quiet = False Then MessageBox.Show("Added parameter " & NewName & " to " & NewGroupName)
		End If

		oDoc.Update()

	End Sub


'### Utility Functions ###'

	Private Sub AddGroup(groupName as String)
		Dim group as CustomParameterGroup
			group = paramGroups.Add(groupName, groupName)
	End Sub

	Private Sub AddParameterToGroup(name as String, group as CustomParameterGroup)
		Try
			Dim oParam As Inventor.Parameter = oParameters(name)
			group.Add(oParam)
		Catch ex As ArgumentException
		End Try
	End Sub

	Private Sub DeleteGroup(group as CustomParameterGroup)
		Try
			group.Delete()
		Catch ex As ArgumentException
		End Try
	End Sub

	Private Function DoesGroupExist(value As String) As Boolean

		dim group As Inventor.CustomParameterGroup
		for each group in paramGroups
			if group.DisplayName = value Then
				return true
			end If
		next

		return false
	End Function

	Private Function DoesGroupContainParameter(value As String, tempGroup As CustomParameterGroup) As Boolean

		dim tempParameter As Inventor.Parameter
		for each tempParameter in tempGroup
			if tempParameter.Name = value Then
				return true
			end If
		next

		return false
	End Function

	Public Function DoesParameterExist(value As String) As Boolean

		dim parameter As Inventor.Parameter
		for each parameter in oParameters
			if parameter.Name = value then
				return true
			end if
		next

		return false
	End Function

	Private Function GetGroupByName(value As String) As Inventor.CustomParameterGroup
		return paramGroups.Item(value)
	End Function

	Private Sub GetParamGroups(doc As Inventor.Document)
		Select Case doc.DocumentType
			Case kPartDocumentObject, kAssemblyDocumentObject
				oParameters = doc.ComponentDefinition.Parameters
			Case kDrawingDocumentObject
				oParameters = doc.Parameters
			Case Else
				Throw New NotImplementedException
		End Select

		paramGroups = oParameters.CustomParameterGroups

	End Sub

	Private Function IsGroupEmpty(group as CustomParameterGroup) As Boolean
		If group.Count = 0 Then
			return true
		Else
			return false
		End If
	End Function

	Private Function ParseGroupName(name As String) As String
		Dim x As integer = instr(name, groupNameDelimiter)
		
		if (x > 0) Then
			return Left(name, x-1)
		Else
			return ""
		end if
	End Function

	Private Function IsParameterGroupFormat(name As String)
		Dim x As integer = instr(name, groupNameDelimiter)

		if (1 < x) And (x < name.Length) Then
			return true
		Else
			return false
		end if
	End Function

	Private Sub RemoveParameterFromGroup(name as String, group as CustomParameterGroup)
		Try
			Dim paramList As IEnumerator = group.GetEnumerator()
			Dim param As Parameter
			For i As Integer = 0 To group.Count Step 1
				paramList.MoveNext()
				If paramList.Current.Name = name
					group.Remove(i + 1)
					Exit For
				End If
			Next
		Catch ex As ArgumentException
		End Try
	End Sub

	Private Function IsValidGroupName(value as String) As Boolean
		Dim testValue As String = ParseGroupName(value)
		If String.IsNullOrWhitespace(testValue) Then
			return false
		Else
			return true
		End If
	End Function


End Class


''' <summary>
''' This object is a shared class pointing to the Inventor.Application object.
''' </summary>
Public Class InventorApp
    Public Shared Property Application As Inventor.Application = GetObject(, "Inventor.Application")
End Class
